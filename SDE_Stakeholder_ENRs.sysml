package <SDE_Stakeholder_ENRs> 'SDE Stakeholder Expectations, Needs, and Requirements' {
	doc /* Stakeholder-owned expressions of their expectations, needs, and requirements */
	
    private import SDE_Profile::*;
    private import DE_Stakeholders::*;
    private import 'Model-Based_Structured_Requirement'::*;
    
    //////////////////////////////
	public import STEELMAN_Requirements::** {
		doc /* The STEELMAN High-Level Language requirements are stakeholder requirements */
	}
    //////////////////////////////
	
	package 'SDE Architecture Tenets' {
		doc /* Architecture tenets or design principles for Seamless Digital Engineering */
		
		concern def <'C-SDE-T.1'> 'Seamless Models' {
			doc /* Engineering models become interoperable with consistent and coherent meta-models */
		}
		
		concern def <'C-SDE-T.2'> 'Composable Data' {
			doc /* Data objects become composable with commensurate data schemas */
		}
		
		concern def <'C-SDE-T.3'> 'Live Objects' {
			doc /* Engineering artifacts maintain bidirectional traceability in a live object system */
		}
		
		concern def <'C-SDE-T.4'> 'Seamless Workflows' {
			doc /* Workflows become consistent and coherent with a unified HCI */
		}
		
		concern def <'C-SDE-T.5'> 'Clean-slate Cybersecurity' {
			doc /* Only a clean-state computer architecture can satisfy these requirements while guaranteeing CIA properties */
		}
	}
	
	//////////
    
    package Conviviality_Concerns {
	    	doc /* Concerns derived from the Matrix of Convivial Technology. */
	    	
	    	concern def <'C-CV.1'> 'Relatedness' {
	    		doc /* What does it bring about between people? */
	    		stakeholder op : DE_Stakeholders::Operator;
	    	}
	    	
	    	concern def <'C-CV.2'> 'Accessibility' {
	    		doc /* Who can product/use it where and how? */
	    		stakeholder op : DE_Stakeholders::Operator;
	    	}
	    	
	    	concern def <'C-CV.3'> 'Adaptability' {
	    		doc /* How independent and linkable is it? */
	    		stakeholder op : DE_Stakeholders::Operator;
	    	}
	    	
	    	concern def <'C-CV.4'> 'Bio-Interaction' {
	    		doc /* How does it interact with living organisms? */
	    		stakeholder op : DE_Stakeholders::Operator;
	    	}
	    	
	    	concern def <'C-CV.5'> 'Appropriateness' {
	    		doc /* What is the relation between input and output considering the context? */
	    		stakeholder op : DE_Stakeholders::Operator;
	    	}
    }
    
    /////////
    
    package Tool_Integration_Concerns {
    		doc /* Concerns derived from I. Thomas and B. A. Nejmeh, “Definitions of tool integration for environments,” IEEE Software, vol. 9, no. 2, pp. 29–35, Mar. 1992, doi: 10.1109/52.120599 */
    		
    		concern def <'C-TI-PRES.1'> 'Appearance and Behavior' {
    			doc /* To what extent do two tools use similar screen appearance and interaction behavior? */
    		}
    		
    		concern def <'C-TI-PRES.2'> 'Interaction Paradigm' {
    			doc /* To what extent do two tools use similar metaphors and mental models? */
    		}
    		
    		concern def <'C-TI-CTRL.1'> 'Provision' {
    			doc /* To what extent are a tool's services used by other tools in the environment? */
    		}
    		
    		concern def <'C-TI-CTRL.2'> 'Use' {
    			doc /* To what extent does a tool use the services provided by other tools in the environment? */
    		}
    		
    		concern def <'C-TI-PROC.1'> 'Process Step' {
    			doc /* How well do relevant tools combine to support the performance of a process step? */
    		}
    		
    		concern def <'C-TI-PROC.2'> 'Event' {
    			doc /* How well do relevant tools agree on the events required to support a process? */
    		}
    		
    		concern def <'C-TI-PROC.3'> 'Constraint' {
    			doc /* How well do relevant tools cooperate to enforce a constraint? */
    		}
    		
    		concern def <'C-TI-DATA.1'> 'Interoperability' {
    			doc /* How much work must be done for a tool to manipulate data produced by another? */
    		}
    		
    		concern def <'C-TI-DATA.2'> 'Non-redundancy' {
    			doc /* How much data managed by a tool is duplicated in or can be derived from the data managed by the other? */
    		}
    		
    		concern def <'C-TI-DATA.3'> 'Data Consistency' {
    			doc /* How well do two tools cooperate to maintain the semantic constraints on the data they manipulate? */
    		}
    		
    		concern def <'C-TI-DATA.4'> 'Data Exchange' {
    			doc /* How much work must be done to make the nonpersistent data generated by one tool usable by the other? */
    		}
    		
    		concern def <'C-TI-DATA.5'> 'Synchronization' {
    			doc /* How well does a tool communicate changes it makes to the values of nonpersistent, common data? */
    		}
    }
    
    /////////
    
    package Tool_Integration_Requirements {
    		doc /* Requirements which frame concerns in the Tool_Integration_Concerns package */
    		
    		#'requirement expression' requirement def <'RSTK-TI-PRES.1'> 'HCI Standard' {
    			doc /* The Seamless DE Tools shall conform to the Seamless DE HCI Standard. */
    			frame concern : Tool_Integration_Concerns::'C-TI-PRES.1';
    		}
    		
    		#'requirement expression' requirement def <'RSTK-TI-PRES.2'> 'Uniform HCI Configuration' {
    			doc /* Following HCI Customization by the Operator, the Seamless DE Appliance shall apply the Operator HCI Configuration uniformly. */
    			frame concern : Tool_Integration_Concerns::'C-TI-PRES.2';
    		}
    		
    		#'requirement expression' requirement def <'RSTK-TI-CTRL.1'> 'System Libraries' {
    			doc /* The Seamless DE Appliance shall provide common functionality as formally-verified System Libraries. */
    			frame concern : Tool_Integration_Concerns::'C-TI-CTRL.1';
    		}
    		
    		#'requirement expression' requirement def <'RSTK-TI-CTRL.2'> 'System Library Reuse' {
    			doc /* The Seamless DE Tools shall reuse System Libraries for Tool-specific functions. */
    			frame concern : Tool_Integration_Concerns::'C-TI-CTRL.2';
    		}
    		
    		#'requirement expression' requirement def <'RSTK-TI-CTRL.3'> 'Tool Interface Standard' {
    			doc /* The Seamless DE Tools shall provide Tool functions conforming to the Seamless DE Tool Interface Standard. */
    			frame concern : Tool_Integration_Concerns::'C-TI-CTRL.2';
    		}
    		
    		#'requirement expression' requirement def <'RSTK-TI-PROC.1'> 'Workflow Definition' {
    			doc /* The Seamless DE Appliance shall provide the Workflow Definition Tool. */
    			frame concern : Tool_Integration_Concerns::'C-TI-PROC.1';
    		}
    		
    		#'requirement expression' requirement def <'RSTK-TI-PROC.2'> 'Process Event Data' {
    			doc /* The Workflow Definition Tool shall define the Process Event using Seamless DE Data Definition Standard. */
    			frame concern : Tool_Integration_Concerns::'C-TI-PROC.2';
    		}
    		
    		#'requirement expression' requirement def <'RSTK-TI-PROC.3'> 'Process Constraint' {
    			doc /* During Workflow Definition & Execution, the Workflow Definition Tool shall enforce the Process Constraint on the Workflow-Defined Tool. */
    			frame concern : Tool_Integration_Concerns::'C-TI-PROC.3';
    		}
    		
    		#'requirement expression' requirement def <'RSTK-TI-DATA.1'> 'Data Schema' {
    			doc /* The Seamless DE Tools shall define the applicable Data Schema conforming to the Seamless DE Data Definition Standard. */
    			frame concern : Tool_Integration_Concerns::'C-TI-DATA.1';
    		}
    		
    		#'requirement expression' requirement def <'RSTK-TI-DATA.2'> 'ACID-Compliant Database' {
    			doc /* The Seamless DE Appliance shall provide the ACID-compliant System Database. */
    			frame concern : Tool_Integration_Concerns::'C-TI-DATA.2';
    		}
    		
    		#'requirement expression' requirement def <'RSTK-TI-DATA.3'> 'Semantic Constraints' {
    			doc /* The Seamless DE Appliance Database shall maintain semantic constraints of data where available. */
    			frame concern : Tool_Integration_Concerns::'C-TI-DATA.3';
    		}
    		
    		#'requirement expression' requirement def <'RSTK-TI-DATA.4'> 'Transactionality' {
    			doc /* The Seamless DE Tools shall write transactions to the Seamless DE Appliance Database for each change performed by the Operator. */
    			frame concern : Tool_Integration_Concerns::'C-TI-DATA.4';
    		}
    		
    		#'requirement expression' requirement def <'RSTK-TI-DATA.5'> 'Transaction Log' {
    			doc /* The Seamless DE Appliance Database shall provide the Transaction Log applicable to the Seamless DE Tool. */
    			frame concern : Tool_Integration_Concerns::'C-TI-DATA.5';
    		}
    }
	
    /////////
	
	package Seven_Laws_of_Sane_Personal_Computing {
		doc /* Datskovskiy's Seven Laws of Sane Personal Computing. Source: http://www.loper-os.org/?p=284 */
		
		comment /* Although described as "laws", these statements read as stakeholder expectations. */
		
		#expectation requirement def <'ESTK-SL-SPC.1'> 'Obeys operator' {
			doc /* Does not interrupt tasks or activities; does not perform side-effects unless clearly defined */
		}
		
		#expectation requirement def <'ESTK-SL-SPC.2'> 'Forgives mistakes' {
			doc /* Infinite `undo'; clear messaging of the source of mistakes as well as advice on how to correct them */
		}
		
		#expectation requirement def <'ESTK-SL-SPC.3'> 'Retains knowledge' {
			doc /* With the modern capacity of RAM and disk space, computers should not forget past actions and data; work drafts are never lost */
		}
		
		#expectation requirement def <'ESTK-SL-SPC.4'> 'Preserves meaning' {
			doc /* The machine does not execute untrusted binary blobs because they cannot be verified to operate in accordance with secure semantics; the machine is an interpreter of high-level language */
		}
		
		#expectation requirement def <'ESTK-SL-SPC.5'> 'Survives disruptions' {
			doc /* Upon encounter of a run-time error, the state is preserved and an interface provided to the operator to recover from the error and continue operation */
		}
		
		#expectation requirement def <'ESTK-SL-SPC.6'> 'Reveals purpose' {
			doc /* All information held within the system is accessible, introspectible, and modifiable by the operator */
		}
		
		#expectation requirement def <'ESTK-SL-SPC.7'> 'Serves loyally' {
			doc /* The machine shall never tell a lie to the operator */
		}
	}
}
