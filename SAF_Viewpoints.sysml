library package <SAF_VP> System_Architecture_Framework_Viewpoints {
	doc /* This package should be organized roughly like follows, with domains and aspects, and viewpoints at their intersection:
	 * 
	 * 00_RA_Development_Domain
	 * ├── 02_Taxonomy_and_Structure
	 * └── 08_Traceability_and_Mapping
	 * 01_Common_Domain
	 * └── 02_Taxonomy_and_Structure
	 * 02_Operational_Domain
	 * ├── 01_Context_and_Exchange
	 * ├── 02_Taxonomy_and_Structure
	 * ├── 03_Process_and_Behavior
	 * ├── 04_Interaction_and_Collaboration
	 * ├── 06_Requirements
	 * └── 08_Traceability_and_Mapping
	 * 03_Functional_Domain
	 * ├── 01_Context_and_Exchange
	 * ├── 02_Taxonomy_and_Structure
	 * ├── 03_Process_and_Behavior
	 * ├── 04_Interaction_and_Collaboration
	 * ├── 05_Interfaces
	 * ├── 06_Requirements
	 * ├── 07_Safety_and_Security
	 * └── 08_Traceability_and_Mapping
	 * 04_Logical_Domain
	 * ├── 02_Taxonomy_and_Structure
	 * ├── 04_Interaction_and_Collaboration
	 * └── 08_Traceability_and_Mapping
	 * 05_Physical_Domain
	 * ├── 01_Context_and_Exchange
	 * ├── 02_Taxonomy_and_Structure
	 * ├── 04_Interaction_and_Collaboration
	 * ├── 05_Interfaces
	 * └── 08_Traceability_and_Mapping */
}
