package SDE_RA {
	/* The Seamless Digital Engineering Reference Architecture (or SDE_RA, for short) is a category reference architecture for digital engineering environments. It is intended to be tailored to an organization's specific context and needs, providing a useful starting point for an organization's migration to digital engineering. It provides SysML v2 language extensions, definitions and usages that may be used in digital engineering practices, including the systems engineering and other lifecycle processes for designing and deploying systems, demonstrated here in the design of an organization's own digital (IT) environment. */
	
	public import SDE_Profile::**;
	public import DE_Stakeholders::**;
	public import DE_Problem_Space::**;
	public import DE_Solutions_Space::**;
	
	public import 'SDE Mission, Goals, Objectives'::**;
	public import 'SDE Stakeholder Expectations, Needs, and Requirements'::**;
	public import SDE_Requirements::**;
	public import SDE_Parts::**;
	public import STEELMAN_Requirements::**;
	public import 'SDE Meta-Language Specification'::**;
	public import Bootstrap_Language_Requirements::**;
	
	public import SDE_RA_Views::**;
}
